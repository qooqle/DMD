module dmd {
    yang-version 1;
    namespace "urn:opendaylight:params:xml:ns:yang:dmd";
    prefix "dmd";

    revision "2015-01-05" {
        description "Initial revision of dmd model";
    }

    container level1 {
    	leaf valiable {
    		type string;
    	}
	container level2 {
    		leaf valiable {
    			type string;
    		}
	}
    }
    rpc dmd-test-api {

        description
            "Set a list of conditions for a particular endpoint group.
             These conditions will apply to all endpoints in the
             endpoint group.  These conditions will be added to the
             existing list of conditions.";

        input {
		leaf input-valiable {
			type string;
		}
        }
        output {
		leaf output-result {
			type string;
		}
        }


    }
}
